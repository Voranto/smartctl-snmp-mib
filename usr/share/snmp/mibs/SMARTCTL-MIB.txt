SMARTCTL-MIB DEFINITIONS ::= BEGIN

-- imports and exports

IMPORTS
	MODULE-COMPLIANCE, OBJECT-GROUP
		FROM SNMPv2-CONF
	MODULE-IDENTITY, OBJECT-TYPE, Integer32, Gauge32
		FROM SNMPv2-SMI
	DisplayString, TruthValue
		FROM SNMPv2-TC
	hackingInternal, hackingExperimental
		FROM HACKING-SNMP-MIB;

smartCtlMIB MODULE-IDENTITY
	LAST-UPDATED	"202603100000Z"
	ORGANIZATION	"Hacking Networked Solutions Ltd"
	CONTACT-INFO	"Max Hacking"
	DESCRIPTION		"This MIB module defines objects for HDD SMART data."
	REVISION		"202603100000Z"
	DESCRIPTION		"Derived from DISKIO-MIB ex UCD."
	::= { smartCtl 1 }

smartCtl				OBJECT IDENTIFIER ::= { hackingExperimental 1 }
smartCtlMIBConformance	OBJECT IDENTIFIER ::= { hackingInternal 1 }

--

smartCtlTable OBJECT-TYPE
	SYNTAX		SEQUENCE OF SsmartCtlEntry
	MAX-ACCESS	not-accessible
	STATUS		current
	DESCRIPTION "Table of HDD SMART information."
	::= { smartCtl 2 }

smartCtlEntry OBJECT-TYPE
	SYNTAX		SsmartCtlEntry
	MAX-ACCESS	not-accessible
	STATUS		current
	DESCRIPTION "An entry containing a device and its statistics."
	INDEX		{ smartCtlDeviceIndex }
	::= { smartCtlTable 1 }
	
	SsmartCtlEntry ::= SEQUENCE {
	smartCtlDeviceIndex						Integer32,
	smartCtlDeviceDev						DisplayString,
	smartCtlDeviceModelFamily				DisplayString,
	smartCtlDeviceDeviceModel				DisplayString,
	smartCtlDeviceSerialNumber				DisplayString,
	smartCtlDeviceUserCapacity				DisplayString,
	smartCtlDeviceATAVersion				DisplayString,
	smartCtlDeviceHealthOK					TruthValue,
	smartCtlDeviceTemperatureCelsius		Gauge32,
	smartCtlDeviceReallocatedSectorCt		Gauge32,
	smartCtlDeviceCurrentPendingSector		Gauge32,
	smartCtlDeviceOfflineUncorrectable		Gauge32,
	smartCtlDeviceUDMACRCErrorCount			Gauge32,
	smartCtlDeviceReadErrorRate				Gauge32,
	smartCtlDeviceSeekErrorRate				Gauge32,
	smartCtlDeviceHardwareECCRecovered		Gauge32,
	smartCtlDeviceFirmwareVersion			DisplayString,
	smartCtlDeviceSSDLifeLeft				Gauge32,
	smartCtlDevicePowerCycleCount			Gauge32,
	smartCtlDevicePowerOnHours				Gauge32,
	smartCtlDeviceWWN                       DisplayString,
	smartCtlDataUnitsRead                   Gauge32,
	smartCtlDataUnitsWritten                Gauge32,
	smartCtlAvailableSpare                  Gauge32,
	smartCtlUnsafeShutdowns                 Gauge32,
	smartCtlDeviceLifetimeUsedPercentage    Gauge32,
	smartCtlDeviceHeliumLevel               Gauge32
}


smartCtlDeviceIndex OBJECT-TYPE
	SYNTAX		Integer32 (0..65535)
	MAX-ACCESS	read-only
	STATUS		current
	DESCRIPTION "Reference index for each observed device."
	::= { smartCtlEntry 1 }

smartCtlDeviceDev OBJECT-TYPE
	SYNTAX		DisplayString
	MAX-ACCESS	read-only
	STATUS		current
	DESCRIPTION "The path to the DEV entry for this device. Example: '/dev/sda'"
	::= { smartCtlEntry 2 }

smartCtlDeviceModelFamily OBJECT-TYPE
	SYNTAX		DisplayString
	MAX-ACCESS	read-only
	STATUS		current
	DESCRIPTION "The Model Family string for this device. Example: 'Seagate Surveillance'"
	::= { smartCtlEntry 3 }

smartCtlDeviceDeviceModel OBJECT-TYPE
	SYNTAX		DisplayString
	MAX-ACCESS	read-only
	STATUS		current
	DESCRIPTION "The Device Model string for this device. Example: 'ST1000VX000-1ES162'"
	::= { smartCtlEntry 4 }

smartCtlDeviceSerialNumber OBJECT-TYPE
	SYNTAX		DisplayString
	MAX-ACCESS	read-only
	STATUS		current
	DESCRIPTION "The Serial Number for this device. Example: 'Z4YE26AA'"
	::= { smartCtlEntry 5 }

smartCtlDeviceUserCapacity OBJECT-TYPE
	SYNTAX		DisplayString
	MAX-ACCESS	read-only
	STATUS		current
	DESCRIPTION "The User Capacity for this device in bytes. Example: '1,000,204,886,016 bytes'"
	::= { smartCtlEntry 6 }

smartCtlDeviceATAVersion OBJECT-TYPE
	SYNTAX		DisplayString
	MAX-ACCESS	read-only
	STATUS		current
	DESCRIPTION "The ATA Version supported by this device. Example: 'ACS-2, ACS-3 T13/2161-D revision 3b'"
	::= { smartCtlEntry 7 }

smartCtlDeviceHealthOK OBJECT-TYPE
	SYNTAX		TruthValue
	MAX-ACCESS	read-only
	STATUS		current
	DESCRIPTION "The current SMART health status reported by this device."
	::= { smartCtlEntry 8 }

smartCtlDeviceTemperatureCelsius OBJECT-TYPE
	SYNTAX		DisplayString
	MAX-ACCESS	read-only
	STATUS		current
	DESCRIPTION "The current Temperature in degrees Celsius of this device."
	::= { smartCtlEntry 9 }

smartCtlDeviceReallocatedSectorCt OBJECT-TYPE
	SYNTAX		Gauge32
	MAX-ACCESS	read-only
	STATUS		current
	DESCRIPTION "The number of Reallocated Sectors on this device. A value other than zero may indicate device failure. "
	::= { smartCtlEntry 10 }

smartCtlDeviceCurrentPendingSector OBJECT-TYPE
	SYNTAX		Gauge32
	MAX-ACCESS	read-only
	STATUS		current
	DESCRIPTION "The number of Current Pending Sectors on this device. A value other than zero may indicate device failure."
	::= { smartCtlEntry 11 }

smartCtlDeviceOfflineUncorrectable OBJECT-TYPE
	SYNTAX		Gauge32
	MAX-ACCESS	read-only
	STATUS		current
	DESCRIPTION "The number of Off-line Uncorrectable Sectors on this device. A value other than zero may indicate device failure."
	::= { smartCtlEntry 12 }

smartCtlDeviceUDMACRCErrorCount OBJECT-TYPE
	SYNTAX		Gauge32
	MAX-ACCESS	read-only
	STATUS		current
	DESCRIPTION "The current UDMA CRC Error Count on this device."
	::= { smartCtlEntry 13 }

smartCtlDeviceReadErrorRate OBJECT-TYPE
	SYNTAX		Gauge32
	MAX-ACCESS	read-only
	STATUS		current
	DESCRIPTION "The current Read Error Rate on this device, normalized. Represents a value between 0 and 255, with 0 being the worst condition,
	            and 255 being the best condition. Most manufacturers use 100 or 200 as a best value."
	::= { smartCtlEntry 14 }

smartCtlDeviceSeekErrorRate OBJECT-TYPE
	SYNTAX		Gauge32
	MAX-ACCESS	read-only
	STATUS		current
	DESCRIPTION "The current Seek Error Rate on this device, normalized. Represents a value between 0 and 255, with 0 being the worst condition,
	            and 255 being the best condition. Most manufacturers use 100 or 200 as a best value."
	::= { smartCtlEntry 15 }

smartCtlDeviceHardwareECCRecovered OBJECT-TYPE
	SYNTAX		Gauge32
	MAX-ACCESS	read-only
	STATUS		current
	DESCRIPTION "The count of errors that could not be recovered using hardware ECC. A value other than zero may indicate device failure. "
	::= { smartCtlEntry 16 }

smartCtlDeviceFirmwareVersion OBJECT-TYPE
	SYNTAX DisplayString
	MAX-ACCESS	read-only
	STATUS		current
	DESCRIPTION "The current Firmware Version installed on this device. Example: 'CV27'"
	::= { smartCtlEntry 17 }

smartCtlDeviceSSDLifeLeft OBJECT-TYPE
	SYNTAX		Gauge32
	MAX-ACCESS	read-only
	STATUS		current
	DESCRIPTION "The current SSD Life Left on this device."
	::= { smartCtlEntry 18 }

smartCtlDevicePowerCycleCount OBJECT-TYPE
	SYNTAX		Gauge32
	MAX-ACCESS	read-only
	STATUS		current
	DESCRIPTION "The current Power Cycle Count on this device."
	::= { smartCtlEntry 19 }

smartCtlDevicePowerOnHours OBJECT-TYPE
	SYNTAX		DisplayString
	MAX-ACCESS	read-only
	STATUS		current
	DESCRIPTION "The current Power On Hours on this device."
	::= { smartCtlEntry 20 }

smartCtlDeviceWWN OBJECT-TYPE
	SYNTAX		DisplayString
	MAX-ACCESS	read-only
	STATUS		current
	DESCRIPTION "Logical Unit WWN Device Identifier for this device. Example: '5000c50092525886'"
	::= { smartCtlEntry 21 }

smartCtlDataUnitsRead OBJECT-TYPE
    SYNTAX      Gauge32
    MAX-ACCESS  read-only
    STATUS      current
    DESCRIPTION "Data units read for this device in Gigabytes. A value of 1 represents 2^30 Bytes"
    ::= { smartCtlEntry 22 }

smartCtlDataUnitsWritten OBJECT-TYPE
    SYNTAX      Gauge32
    MAX-ACCESS  read-only
    STATUS      current
    DESCRIPTION "Data units written for this device in Gigabytes. A value of 1 represents 2^30 Bytes."
    ::= { smartCtlEntry 23 }

smartCtlAvailableSpare OBJECT-TYPE
    SYNTAX      Gauge32
    MAX-ACCESS  read-only
    STATUS      current
    DESCRIPTION "Percentage of the spare sectors still available
                for this device. A low value may indicate that the device is failing."
    ::= { smartCtlEntry 24 }

smartCtlUnsafeShutdowns OBJECT-TYPE
    SYNTAX      Gauge32
    MAX-ACCESS  read-only
    STATUS      current
    DESCRIPTION "Unsafe shutdown count for this device"
    ::= { smartCtlEntry 25 }

smartCtlDeviceLifetimeUsedPercentage OBJECT-TYPE
    SYNTAX      Gauge32
    MAX-ACCESS  read-only
    STATUS      current
    DESCRIPTION "Percentage used of the lifetime of the device. A value of 100 indicates that
                 the device has reached its theoretical end of life, not that has malfunctioned. The value may go up
                 to 255."
    ::= { smartCtlEntry 26 }

smartCtlDeviceHeliumLevel OBJECT-TYPE
    SYNTAX      Gauge32
    MAX-ACCESS  read-only
    STATUS      current
    DESCRIPTION "Value from 0 to 100 representing the helium level of the device. 100 is the ideal value
                 0 is the worst possible value"
    ::= { smartCtlEntry 27 }

-- Conformance information ******************************************

smartCtlMIBCompliances OBJECT IDENTIFIER ::= {smartCtlMIBConformance 1}
smartCtlMIBGroups	   OBJECT IDENTIFIER ::= {smartCtlMIBConformance 2}

-- Compliance statements

smartCtlCompliance MODULE-COMPLIANCE
	STATUS		 current
	DESCRIPTION "The compliance statement for SNMP entities which
				 implement the SMARTCTL-MIB."

	MODULE	  -- this module
		MANDATORY-GROUPS { smartCtlGroup }
	::= { smartCtlMIBCompliances 1 }

smartCtlGroup OBJECT-GROUP
	OBJECTS 
	{
		smartCtlDeviceIndex,
		smartCtlDeviceDev,
		smartCtlDeviceModelFamily,
		smartCtlDeviceDeviceModel,
		smartCtlDeviceSerialNumber,
		smartCtlDeviceUserCapacity,
		smartCtlDeviceATAVersion,
		smartCtlDeviceHealthOK,
		smartCtlDeviceTemperatureCelsius,
		smartCtlDeviceReallocatedSectorCt,
		smartCtlDeviceCurrentPendingSector,
		smartCtlDeviceOfflineUncorrectable,
		smartCtlDeviceUDMACRCErrorCount,
		smartCtlDeviceReadErrorRate,
		smartCtlDeviceSeekErrorRate,
		smartCtlDeviceHardwareECCRecovered,
		smartCtlDeviceFirmwareVersion,
		smartCtlDeviceSSDLifeLeft,
		smartCtlDevicePowerCycleCount,
		smartCtlDevicePowerOnHours
	}
	STATUS		 current
	DESCRIPTION "A collection of objects providing for remote
				 monitoring of HDD SMART data."
	::= { smartCtlMIBGroups 1 }
	
END
